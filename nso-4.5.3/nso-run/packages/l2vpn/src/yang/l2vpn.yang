module l2vpn {
  namespace "http://com/example/l2vpn";
  prefix l2vpn;

  import ietf-inet-types {
    prefix inet;
  }
  import tailf-ncs {
    prefix ncs;
  }
  import tailf-common {
     prefix tailf;
  }

 augment /ncs:services {
  list l2vpn {
    key name;
    unique pw-id;

    uses ncs:service-data;
    ncs:servicepoint "l2vpn";

    leaf name {
      tailf:info "Service Instance Name";
      type string;
    }

    leaf customer {
      tailf:info "Customer Name";
      type leafref {
         path "/ncs:customers/ncs:customer/ncs:id";
      }
    }

    leaf pw-id {
       tailf:info "Unique Pseudowire ID";
       mandatory true;
       type uint32 {
          range "1..4294967295";
       }
    }

    leaf device1 {
       tailf:info "PE Router1";
       mandatory true;
       type leafref {
          path "/ncs:devices/ncs:device/ncs:name";
       }
    }

    leaf intf-number1 {
      tailf:info "GigabitEthernet Interface ID";
      mandatory true;
      type string {
         pattern "[0-9]{1,2}(/[0-9]{1,2}){1,4}";
      }
    }

    leaf remote-ip1 {
       tailf:info "Loopback0 IP Address of Remote PE (10.0.0.X)";
       mandatory true;
       type inet:ipv4-address {
           pattern "10\\.0\\.0\\.[0-9]+";
       }
    }

    leaf device2 {
      tailf:info "PE Router2";
      mandatory true;
      type leafref {
         path "/ncs:devices/ncs:device/ncs:name";
      }
    }

    leaf intf-number2 {
       tailf:info "GigabitEthernet Interface ID";
       mandatory true;
       type string {
          pattern "[0-9]{1,2}(/[0-9]{1,2}){1,4}";
       }
    }

    leaf remote-ip2 {
       tailf:info "Loopback0 IP Address of Remote PE (10.0.0.X)";
       mandatory true;
       type inet:ipv4-address {
          pattern "10\\.0\\.0\\.[0-9]+";
       }
    }
  }
  }
}
