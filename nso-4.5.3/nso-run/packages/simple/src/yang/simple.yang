module simple {
  namespace "http://com/example/simple";
  prefix simple;

  import ietf-inet-types {
    prefix inet;
  }
  import tailf-ncs {
    prefix ncs;
  }

 augment "/ncs:services" {
  list simple {
    key "name";
    unique "ip-address";

    uses ncs:service-data;
    ncs:servicepoint "simple";

    leaf name {
      type string;
    }

    leaf ip-address{
        mandatory true;
        type inet:ipv4-address {
           pattern "10\\.0\\.0\\.[0-9]+";
        }
    }
    leaf port{
        mandatory true;
        type uint32 {
            range "0..65535";
        }
    }

    // may replace this with other ways of refering to the devices.
    leaf-list device {
      type leafref {
        path "/ncs:devices/ncs:device/ncs:name";
      }
    }

    // replace with your own stuff here
    leaf dummy {
      type inet:ipv4-address;
    }
  }
  }
}
