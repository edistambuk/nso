module novi_servis {
  namespace "http://com/example/novi_servis";
  prefix novi_servis;

  import ietf-inet-types {
    prefix inet;
  }
  import tailf-ncs {
    prefix ncs;
  }

  import tailf-common {
    prefix tailf;
  }

  augment /ncs:services {
  list ovako_ja_njega_vidim_u_terminalu {
    key name;
    unique pw-id;

    uses ncs:service-data;
    ncs:servicepoint "novi_servis";

    leaf name {
      type string;
    }

    leaf pw-id {
      mandatory true;
      type uint32;
    }

    leaf device1 {
       tailf:info "PE Router1";
       mandatory true;
       type leafref {
         path "/ncs:devices/ncs:device/ncs:name";
       }
    }

    leaf intf-number1 {
       tailf:info "GigabitEthernet Interface ID";
       mandatory true;
       type string {
          pattern "[0-9]{1,2}(/[0-9]{1,2}){1,3}";
       }
    }

    leaf remote-ip1 {
        tailf:info "Loopback0 IP Address of Remote PE (10.0.0.X)";
        mandatory true;
        type inet:ipv4-address {
            pattern  "10\\.0\\.0\\.[0-9]+";
        }
    }

    leaf device2 {
       tailf:info "PE Router2";
       mandatory true;
       type leafref {
          path "/ncs:devices/ncs:device/ncs:name";
       }
    }

    leaf intf-number2 {
       tailf:info "GigabitEthernet Interface ID";
       mandatory true;
       type string {
         pattern "[0-9]{1,2}(/[0-9]{1,2}){1,4}";
       }
    }

    leaf remote-ip2 {
        tailf:info "Loopback0 IP Address of Remote PE (10.0.0.X)";
        mandatory true;
        type inet:ipv4-address {
           pattern "10\\.0\\.0\\.[0-9]+";
        }
    }

  }
  }
}
